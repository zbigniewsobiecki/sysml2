package AllTypes {
    /* Definitions */
    attribute def AttrDef;
    part def PartDef;
    port def PortDef;
    item def ItemDef;
    connection def ConnDef;
    action def ActionDef;
    state def StateDef;
    constraint def ConstraintDef;
    requirement def RequirementDef;
    calc def CalcDef;

    /* Usages */
    attribute attr;
    part myPart;
    port myPort;
    item myItem;
    action myAction;
    state myState;
    constraint myConstraint;
    requirement myReq;
    calc myCalc;
}
